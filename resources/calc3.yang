module calculator {
  namespace       "http://brocade.com/ns/calculator";
  contact         "Alan Thompson <athomps@brocade.com>";
  description     "YANG spec for a simple RPN calculator";
  revision 2017-04-01 {
      description "Prototype 1.0";
  }

  grouping complex-grp {
    description "A complex number";
    leaf real {
      type decimal64; }
    leaf imag {
      type decimal64; } }

  rpc add {
    description "Add 2 numbers";
    input {
      leaf x { 
        type decimal64; }
      leaf y { 
        type decimal64; } }
    output {
      leaf result { 
        type decimal64; } } } 

  rpc addc {
    description "Add 2 numbers";
    input {
      container x { 
        uses complex-grp; }
      container y { 
        uses complex-grp; } }
    output {
      container result {
        uses complex-grp; } } }
}
