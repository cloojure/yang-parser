module brocade-rbridge {
  namespace "urn:brocade.com:mgmt:brocade-rbridge";
  prefix rbridge;

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is an instrumentation to manage 
     rbridge-id feature.";

  revision 2011-06-21 {
    description
      "Initial version of this management module
       brocade-rbridge.";
  }

  typedef raslog-console {
    type enumeration {
      enum INFO {
        value 1;
      }
      enum ERROR {
        value 2;
      }
      enum WARNING {
        value 3;
      }
      enum CRITICAL {
        value 4;
      }
    }
  }

  list rbridge-id {
    key  rbridge-id;
    leaf rbridge-id {
      type uint32;
    }
    leaf swbd-number {
      type int32;
      config false;
    }
    container interface-nodespecific {
      leaf ns-vlan {
        type int32;
      }
      leaf ns-ethernet {
        type int32;
      }
    }
    container ip {
      description
        "Internet Protoccol (IP). ";
    }
    container ipv6 {
      description
        "Internet Protoccol (IPv6). ";
    }
    container router {
      description
        "The routing system.";
    }
    container switch-attributes {
      leaf chassis-name {
        type string {
          length "1..30";
        }
      }
      leaf host-name {
        type string {
          length "1..30";
        }
      }
    }
  }
}
